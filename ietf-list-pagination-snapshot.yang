module ietf-list-pagination-snapshot {
  yang-version 1.1;
  namespace
    "urn:ietf:params:xml:ns:yang:ietf-list-pagination-snapshot";
  prefix lpgsnap;

  import ietf-datastores {
    prefix ds;
    reference
      "RFC 8342: Network Management Datastore Architecture (NMDA)";
  }

  import ietf-netconf {
    prefix nc;
    reference
      "RFC 6241: Network Configuration Protocol (NETCONF)";
  }

  import ietf-netconf-nmda {
    prefix ncds;
    reference
      "RFC 8526: NETCONF Extensions to Support the
                 Network Management Datastore Architecture";
  }

  import ietf-system-capabilities  {
    prefix sysc;
    reference
      "RFC 9691: YANG Modules Describing Capabilities for Systems and
                 Datastore Update Notifications";
  }

  import ietf-list-pagination {
    prefix lpg;
    reference
      "draft-ietf-list-pagination: List Pagination for YANG-driven
                                   Protocols";
  }

  organization
    "IETF NETCONF (Network Configuration) Working Group";

  contact
    "WG Web:   https://datatracker.ietf.org/wg/netconf
     WG List:  NETCONF WG list <mailto:netconf@ietf.org>";

  description
    "This module is used by servers to indicate they support
     snapshot pagination on 'config false' nodes of type 'list'
     and 'leaf-list'. It also defines a grouping for the snapshot
     parameter.

     Copyright (c) 2024 IETF Trust and the persons identified
     as authors of the code. All rights reserved.

     Redistribution and use in source and binary forms, with
     or without modification, is permitted pursuant to, and
     subject to the license terms contained in, the Revised
     BSD License set forth in Section 4.c of the IETF Trust's
     Legal Provisions Relating to IETF Documents
     (https://trustee.ietf.org/license-info).

     This version of this YANG module is part of RFC XXXX
     (https://www.rfc-editor.org/info/rfcXXXX); see the RFC
     itself for full legal notices.

     The key words 'MUST', 'MUST NOT', 'REQUIRED', 'SHALL',
     'SHALL NOT', 'SHOULD', 'SHOULD NOT', 'RECOMMENDED',
     'NOT RECOMMENDED', 'MAY', and 'OPTIONAL' in this document
     are to be interpreted as described in BCP 14 (RFC 2119)
     (RFC 8174) when, and only when, they appear in all
     capitals, as shown here.";

  revision YYYY-MM-DD {
    description
      "Initial revision.";
    reference
      "RFC XXXX: List Pagination Snapshots for YANG-driven
                 Protocols";
  }


  // Identities

  identity snapshot-not-supported {
    base lpg:list-pagination-error;
    description
      "Snapshot is not supported for the target. Either it is not a
       'config false' list or leaf-list, or it is disabled.";
  }

  // Groupings

  grouping snapshot-param-grouping {
    description
      "This grouping may be used by protocol-specific YANG modules
       to define a protocol-specific query parameter.";
    leaf snapshot {
      type boolean;
      description
        "The 'snapshot' parameter indicates that the client requests
         the server to take a snapshot of the 'config false' list or
         leaf-list target before paginating.";
    }
  }

  // Protocol-accessible nodes

  augment "/nc:get/nc:input" {
    description
      "Allow the 'get' operation to use the 'snapshot' query
       parameter for YANG list or leaf-list that is to be
       retrieved.";
    uses snapshot-param-grouping;
  }

  augment "/nc:get-config/nc:input" {
    description
      "Allow the 'get-config' operation to use the 'snapshot' query
       parameter for YANG list or leaf-list that is to be
       retrieved.";
    uses snapshot-param-grouping;
  }

  augment "/ncds:get-data/ncds:input" {
    description
      "Allow the 'get-data' operation to use the 'snapshot' query
       parameter for YANG list or leaf-list that is to be
       retrieved.";
    uses snapshot-param-grouping;
  }

  augment
    "/sysc:system-capabilities/sysc:datastore-capabilities"
    + "/sysc:per-node-capabilities" {

    // Ensure the following node is only used for the
    // <operational> datastore.
    when "/sysc:system-capabilities/sysc:datastore-capabilities"
         + "/sysc:datastore = 'ds:operational'";

    description
      "Defines some leafs that MAY be used by the server to
       describe constraints imposed of the 'where' filters and
       'sort-by' parameters used in list pagination queries.";
    leaf snapshot {
      type empty;
      description
        "Indicates that snapshots are supported for the targeted
         'config false' list or leaf-list node.";
    }
  }
}
